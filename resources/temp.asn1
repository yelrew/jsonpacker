test {}

DEFINITIONS EXPLICIT TAGS ::=

BEGIN

TestStruct ::= SEQUENCE {
        r1	INTEGER,
        r2	INTEGER,
        r3	INTEGER,
        r4	INTEGER,
        r5	INTEGER,
        r6	INTEGER,
        r7	INTEGER,
        r8	INTEGER,
        r9	INTEGER
}

END
